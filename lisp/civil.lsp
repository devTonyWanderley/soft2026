;|HEADER|;

;|	PARÂMETROS	|;
(setq #param-leitura '(("PONTO" "Abrir arquivo de pontos" "C:/Tony/Soft/soft2026/Instâncias/" "pdw")		;	C:\2026\Soft\Instâncias C:/Tony/Soft/soft2026/Instâncias/
		       ("ARESTA" "Abrir arquivo de arestas" "C:/Tony/Soft/soft2026/Instâncias/" "ars")
		       ("FACE" "Abrir arquivo de faces" "C:/Tony/Soft/soft2026/Instâncias/" "sup")
		       ("CONTORNO" "Abrir arquivo de faces" "C:/Tony/Soft/soft2026/Instâncias/" "con")
		       )
      #param-export '(("PONTO" "Salvar arquivo de pontos" "C:/Tony/Soft/soft2026/Instâncias/" "pdw")
		      ("ARESTA" "Salvar arquivo de arestas" "C:/Tony/Soft/soft2026/Instâncias/" "ars")
		      ("FACE" "Salvar arquivo de faces" "C:/Tony/Soft/soft2026/Instâncias/" "sup")
		      ("CONTORNO" "Abrir arquivo de faces" "C:/Tony/Soft/soft2026/Instâncias/" "con")
		      )
      #param-desenho '(("PONTO" "_Pontos" 0.1)
		       ("ARESTA" "_Arestas")
		       ("FACE" "_Faces")
		       ("CONTORNO" "_Contornos")
		       )
      #includes '("io_desenho.LSP" "arquivo.LSP" "desenho.LSP" "texto.LSP")
      )

;|	ROTINA DE INICIALIZAÇÃO	|;
(defun civil:inicia(/ i)
  (while (nth (setq i (if i (1+ i) 0)) #param-leitura)
    (regapp (car (nth i #param-leitura)))
    )
  (setq i nil)
  (while (nth (setq i (if i (1+ i) 0)) #includes)
    (load (strcat "C:/Tony/Soft/soft2026/lisp/" (nth i #includes)))		;	C:/Tony/Soft/soft2026/lisp
    )
  (princ "\nEventuais repetições no desenho:\n\tPontos:")
  (setq #pontos (civil:ler-pontos-do-desenho))
  (princ "\n\n\tArestas:")
  (setq #arestas (civil:ler-arestas-do-desenho))
  (princ "\n\n\tContornos:")
  (setq #contornos (civil:ler-contornos-do-desenho))
  (princ "\n\nCivil carregado com sucesso")
  )

;|	ROTINAS DE LIGAÇÃO	|;
(defun civil:lança-pontos(3d / lt i)
  (setvar "pdmode" 35)
  (setvar "pdsize" (caddr (assoc "PONTO" #param-desenho)))
  (if (setq lt (civil:ler-arquivo "PONTO"))
    (while (nth (setq i (if i (1+ i) 0)) lt)
      (civil:faz-point (civil:ler-ln-ponto (nth i lt)) (cadr (assoc "PONTO" #param-desenho)) 3d)
      )
    (princ "erro ao lançar pontos")
    )
  (civil:ler-pontos-do-desenho)
  (civil:ler-arestas-do-desenho)
  (princ)
  )

(defun civil:lança-pontos-por-atr(3d / lt i a)
  (setvar "pdmode" 35)
  (setvar "pdsize" (caddr (assoc "PONTO" #param-desenho)))
  (if (setq lt (civil:ler-arquivo "PONTO"))
    (while (nth (setq i (if i (1+ i) 0)) lt)
      (setq a (civil:ler-ln-ponto (nth i lt))
	    a (civil:faz-point a (strcat "_" (cadr a)) 3d)
	    )
      )
    (princ "erro ao lançar pontos")
    )
  (civil:ler-pontos-do-desenho)
  (princ)
  )

;|	ROTINAS DE CHAMADA	|;

(defun c:lança-pontos-2d()(civil:lança-pontos nil))
  
(defun c:lança-pontos-3d()(civil:lança-pontos 't))

(defun c:lança-pontos-atr-2d()(civil:lança-pontos-por-atr nil))
  
(defun c:lança-pontos-atr-3d()(civil:lança-pontos-por-atr 't))
  
(defun c:cotas-e-atributos()(civil:mostra-cotas-e-atrs))
  
(defun c:faz-arestas(/ lt)
  (while (setq lt (civil:select-pra-aresta))
    (civil:faz-arestas lt)
    )
  (princ)
  )

(defun c:exporta-pontos()
  (civil:ler-pontos-do-desenho)
  (civil:exportar-arquivo "PONTO" (mapcar 'civil:ln-ponto-export #pontos))
  (princ)
  )

(defun c:exporta-arestas()
  (civil:ler-arestas-do-desenho)
  (civil:exportar-arquivo "ARESTA" (mapcar 'civil:ln-aresta-export #arestas))
  (princ)
  )

(defun c:importar-contorno(/ id lt)
  (if (/= (setq id (getstring "Nome do contorno")) "")
    (if (setq lt (civil:ler-arquivo "CONTORNO"))
      (setq lt (civil:ler-ln-contorno lt)
	    #contornos (cons (cons id lt) #contornos)
	    )
      )
    (alert "cancelado")
    )
  (princ)
  )

(defun c:importar-pontos-append(/ lt)
  (if (setq lt (civil:ler-arquivo "PONTO"))
    (if (setq lt (mapcar 'civil:ler-ln-ponto lt))
      (setq #pontos (append lt #pontos))
      )
    )
  (if #pontos (setq #pontos (civil:elimina-repetição #pontos)))
  (princ)
  )

(defun c:desenhar-contorno(/ n)
  (if #pontos
    (if #contornos
      (progn
	(if (> (length #contornos) 1)
	  (alert "criar rotina pra escolher o contorno a desenhar\natravez do n")
	  (setq n 0)
	  )
	(if n (civil:desenha-contorno (nth n #contornos)))
	)
      (alert "#contornos vazia")
      )
    (alert "#pontos vazia")
    )
  (princ)
  )

;;;--ADEQUAÇÃO 18-01-26--
(defun c:lança-pdw( / lt i)
  (setvar "pdmode" 35)
  (setvar "pdsize" (caddr (assoc "PONTO" #param-desenho)))
  (if (setq lt (civil:ler-arquivo "PONTO"))
    (while (nth (setq i (if i (1+ i) 0)) lt)
      (civil:faz-point (civil:ler-ln-pdw (nth i lt)) (cadr (assoc "PONTO" #param-desenho)) nil)
      )
    (princ "erro ao lançar pontos")
    )
  (civil:ler-pontos-do-desenho)
  (civil:ler-arestas-do-desenho)
  (princ)
  )

(civil:inicia)

;|CATÁLOGO
	civil:inicia(/ i)
	civil:lança-pontos(3d / lt i)
	civil:lança-pontos-por-atr(3d / lt i a)
	c:lança-pontos-2d()
	c:lança-pontos-3d()
	c:lança-pontos-atr-2d()
	c:lança-pontos-atr-3d()
	c:cotas-e-atributos()
	c:faz-arestas(/ lt)
	c:exporta-pontos()
	c:exporta-arestas()
	c:importar-contorno(/ id lt)
	c:importar-pontos-append(/ lt)
	c:desenhar-contorno(/ n)
|;

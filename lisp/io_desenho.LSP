;|HEADER|;
(defun civil:ler-xdata(en)
  (if (setq en (assoc -3
		      (if (listp en)
			(if (= (type (car en)) 'ename)
			  (entget (car en) (mapcar 'car #param-leitura))
			  en
			  )
			(entget en (mapcar 'car #param-leitura))
			)
		      )
	    )
    (mapcar 'cdr (cdadr en))
    )
  )

(defun civil:tipo-de-xdata(en)
  (if (setq en (assoc -3
		      (if (listp en)
			(if (= (type (car en)) 'ename)
			  (entget (car en) (mapcar 'car #param-leitura))
			  en
			  )
			(entget en (mapcar 'car #param-leitura))
			)
		      )
	    )
    (caadr en)
    )
  )

(defun civil:elimina-repetição(arg / r)
  (while (cdr arg)
    (progn
      (if (null (member (car arg) (cdr arg)))
	(setq r (cons (car arg) r))
	(print (car arg))
	)
      (setq arg (cdr arg))
      )
    )
  (cons (car arg) r)
  )

(defun civil:varre-xdata(tipo / en len)
  (while (setq en (if en (entnext en) (entnext)))
    (if (= (civil:tipo-de-xdata en) tipo)
      (setq len (cons (civil:ler-xdata en) len))
      )
    )
  (civil:elimina-repetição len)
  )

(defun civil:ler-pontos-do-desenho(/ a)
  (if (car (setq a (civil:varre-xdata "PONTO")))
    (setq #pontos a)
    (setq #pontos nil)
    )
  )

(defun civil:ler-arestas-do-desenho(/ a)
  (if (car (setq a (civil:varre-xdata "ARESTA")))
    (setq #arestas a)
    (setq #arestas nil)
    )
  )

(defun civil:ler-contornos-do-desenho(/ a)
  (if (car (setq a (civil:varre-xdata "CONTORNO")))
    (setq #contornos a)
    (setq #contornos nil)
    )
  )

(defun civil:select-pra-aresta(/ n en lt)
  (while (< (setq n (if n n 0)) 6)
    (if (setq en (entsel "\nSelecione"))
      (if (= (civil:tipo-de-xdata en) "PONTO")
	(setq n (+ n 2)
	      lt (cons (civil:ler-xdata en) lt)
	      )
	(if (= (civil:tipo-de-xdata en) "ARESTA")
	  (setq n (+ n 2)
		lt (cons (civil:ler-xdata en) lt)
		)
	  )
	)
      (setq n (+ n 7))
      )
    )
  lt
  )

;|CATÁLOGO
	civil:ler-xdata(en)
	civil:tipo-de-xdata(en)
	civil:elimina-repetição(arg / r)
	civil:varre-xdata(tipo / en len)
	civil:ler-pontos-do-desenho(/ a)
	civil:ler-arestas-do-desenho(/ a)
	civil:ler-contornos-do-desenho(/ a)
	civil:select-pra-aresta(/ n en lt)
|;

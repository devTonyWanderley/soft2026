(defun civil:faz-point(arg la 3d)
  (entmake (list (cons 0 "POINT") (cons 8 la)
		 (list 10 (nth 2 arg) (nth 3 arg) (if 3d (nth 4 arg) 0.0))
		 (list -3
		       (list "PONTO"
			     (cons 1000 (car arg))
			     (cons 1000 (cadr arg))
			     (cons 1010 (cddr arg))
			     )
		       )
		 )
	   )
  )

(defun civil:mostra-cotas-e-atrs(/ lt i x y h tx)
  (if (setq lt (civil:varre-xdata "PONTO"))
    (while (nth (setq i (if i (1+ i) 0)) lt)
      (progn
	(setq x (+ (car (last (nth i lt))) (* (caddr (assoc "PONTO" #param-desenho)) 0.7))
	      y (- (cadr (last (nth i lt))) (* (caddr (assoc "PONTO" #param-desenho)) 2.5))
	      h (* 1.5 (caddr (assoc "PONTO" #param-desenho)))
	      tx (rtos (last (last (nth i lt))) 2 3)
	      )
	(entmake (list (cons 0 "TEXT") (cons 8 "_Cotas") (list 10 x y 0.0) (cons 40 h) (cons 1 tx)))
	(setq y (+ y (* (caddr (assoc "PONTO" #param-desenho)) 1.75))
	      tx (car (nth i lt))
	      )
	(entmake (list (cons 0 "TEXT") (cons 8 "_Nomes") (list 10 x y 0.0) (cons 40 h) (cons 1 tx)))
	(setq y (+ y (* (caddr (assoc "PONTO" #param-desenho)) 1.75))
	      tx (cadr (nth i lt))
	      )
	(entmake (list (cons 0 "TEXT") (cons 8 "_Atributos") (list 10 x y 0.0) (cons 40 h) (cons 1 tx)))
	)
      )
    )
  (princ)
  )

(defun civil:faz-aresta(p0 p1 / p)
  (if (> (last (last p0)) (last (last p1))) (setq p p0 p0 p1 p1 p))
  (entmake (list (cons 0 "LINE") (cons 8 "_Arestas")
		 (cons 10 (reverse (cons 0.0 (cdr (reverse (last p0))))))
		 (cons 11 (reverse (cons 0.0 (cdr (reverse (last p1))))))
		 (list -3 (list "ARESTA" (cons 1000 (car p0)) (cons 1000 (car p1))))
		 )
	   )
  (princ)
  )

(defun civil:faz-arestas(arg / a b c d)
  (if (> (length arg) 1)
    (if (< (length arg) 3)	;	2 elementos
      (if (> (length (car arg)) 2)	;	2e & (p, ?)
	(if (> (length (cadr arg)) 2)	;	2e & (p, p)
	  (civil:faz-aresta (car arg) (cadr arg))
	  (progn	;	2e & (p, a)
	    (civil:faz-aresta (car arg) (assoc (car (cadr arg)) #pontos))
	    (civil:faz-aresta (car arg) (assoc (cadr (cadr arg)) #pontos))
	    )
	  )
	(if (> (length (cadr arg)) 2)	;	2e & (a, p)
	  (progn
	    (civil:faz-aresta (assoc (car (car arg)) #pontos) (cadr arg))
	    (civil:faz-aresta (assoc (cadr (car arg)) #pontos) (cadr arg))
	    )
	  (progn	;	2e & (a, a)
	    (setq a (assoc (car (car arg)) #pontos)
		  b (assoc (cadr (car arg)) #pontos)
		  c (assoc (car (cadr arg)) #pontos)
		  d (assoc (cadr (cadr arg)) #pontos)
		  )
	    (if (inters (last a) (last c) (last b) (last d))
	      (progn
		(civil:faz-aresta a c)
		(civil:faz-aresta b c)
		(civil:faz-aresta a d)
		)
	      (progn
		(civil:faz-aresta a c)
		(civil:faz-aresta b d)
		(civil:faz-aresta a d)
		)
	      )
	    )
	  )
	)
      (if (> (length (car arg)) 2)	;	3e & (p, ?, ?)
	(if (> (length (cadr arg)) 2)	;	3e & (p, p, ?)
	   (if (> (length (caddr arg)) 2)	;	3e & (p, p, p)
	     (progn
	       (civil:faz-aresta (car arg) (cadr arg))
	       (civil:faz-aresta (car arg) (caddr arg))
	       (civil:faz-aresta (cadr arg) (caddr arg))
	       )
	     (progn	;	3e & (p, p, a)
	       (setq a (car arg)
		     b (cadr arg)
		     c (assoc (car (caddr arg)) #pontos)
		     d (assoc (cadr (caddr arg)) #pontos)
		     )
	       (if (inters (reverse (cdr (reverse (last a))))
			   (reverse (cdr (reverse (last b))))
			   (reverse (cdr (reverse (last c))))
			   (reverse (cdr (reverse (last d))))
			   )
		 (progn
		   (civil:faz-aresta a c)
		   (civil:faz-aresta a d)
		   (civil:faz-aresta b c)
		   (civil:faz-aresta b d)
		   )
		 (progn
		   (civil:faz-aresta a b)
		   (civil:faz-aresta a c)
		   (civil:faz-aresta a d)
		   (if (inters (reverse (cdr (reverse (last a))))
			       (reverse (cdr (reverse (last c))))
			       (reverse (cdr (reverse (last b))))
			       (reverse (cdr (reverse (last d))))
			       )
		     (civil:faz-aresta b c)
		     (civil:faz-aresta b d)
		     )
		   )
		 )
	       )
	     )
	  (progn	;	3e & (p, a, p)
	    (setq a (car arg)
		  b (caddr arg)
		  c (assoc (car (cadr arg)) #pontos)
		  d (assoc (cadr (cadr arg)) #pontos)
		  )
	    (if (inters (reverse (cdr (reverse (last a))))
			(reverse (cdr (reverse (last b))))
			(reverse (cdr (reverse (last c))))
			(reverse (cdr (reverse (last d))))
			)
	      (progn
		(civil:faz-aresta a c)
		(civil:faz-aresta a d)
		(civil:faz-aresta b c)
		(civil:faz-aresta b d)
		)
	      (progn
		(civil:faz-aresta a b)
		(civil:faz-aresta a c)
		(civil:faz-aresta a d)
		(if (inters (reverse (cdr (reverse (last a))))
			    (reverse (cdr (reverse (last c))))
			    (reverse (cdr (reverse (last b))))
			    (reverse (cdr (reverse (last d))))
			    )
		  (civil:faz-aresta b c)
		  (civil:faz-aresta b d)
		  )
		)
	      )
	    )
	  )
	(progn	;	3e & (a, p, p)
	  (setq a (cadr arg)
		b (caddr arg)
		c (assoc (car (car arg)) #pontos)
		d (assoc (cadr (car arg)) #pontos)
		)
	  (if (inters (reverse (cdr (reverse (last a))))
		      (reverse (cdr (reverse (last b))))
		      (reverse (cdr (reverse (last c))))
		      (reverse (cdr (reverse (last d))))
		      )
	    (progn
	      (civil:faz-aresta a c)
	      (civil:faz-aresta a d)
	      (civil:faz-aresta b c)
	      (civil:faz-aresta b d)
	      )
	    (progn
	      (civil:faz-aresta a b)
	      (civil:faz-aresta a c)
	      (civil:faz-aresta a d)
	      (if (inters (reverse (cdr (reverse (last a))))
			  (reverse (cdr (reverse (last c))))
			  (reverse (cdr (reverse (last b))))
			  (reverse (cdr (reverse (last d))))
			  )
		(civil:faz-aresta b c)
		(civil:faz-aresta b d)
		)
	      )
	    )
	  )
	)
      )
    )
  )

(defun civil:desenha-contorno(arg / i lxd lp lt a)
  (while (nth (setq i (if i (1+ i) 0)) arg)
    (progn
      (setq lxd (cons (cons 1000 (nth i arg)) lxd))
      (if (> i 0)
	(setq a (assoc (nth i arg) #pontos)
	      lp (cons (list 10 (nth 2 a) (nth 3 a)) lp)
	      )
	)
      )
    )
  (setq lxd (list -3 (cons "CONTORNO" (reverse lxd)))
	lt (list (cons 0 "LWPOLYLINE")
		 (cons 100 "AcDbEntity")
		 (cons 8 (strcat "_" (car arg)))
		 (cons 100 "AcDbPolyline")
		 (cons 90 (length lp))
		 (cons 70 1)
		 (cons 43 0.0)
		 (cons 38 0.0)
		 (cons 39 0.0)
		 )
	arg nil
	i nil
	)
  (while (nth (setq i (if i (1+ i) 0)) lp)
    (setq arg (append
		(list
		  (nth i lp)
		  (cons 40 0.0)
		  (cons 41 0.0)
		  (cons 42 0.0)
		  (cons 91 0)
		  )
		arg
		)
	  )
    )
  (setq lt (append lt arg))
  (entmake (append lt (list lxd)))
  )

;|CATÁLOGO
	civil:faz-point(arg la 3d)
	civil:mostra-cotas-e-atrs(/ lt i x y h tx)
	civil:faz-aresta(p0 p1 / p)
	civil:faz-arestas(arg / a b c d)
|;
